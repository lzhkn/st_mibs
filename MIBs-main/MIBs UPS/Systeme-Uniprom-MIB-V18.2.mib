--
-- Systeme-Uniprom-MIB-V1.8.my
-- MIB generated by MG-SOFT Visual MIB Builder Version 6.0  Build 88
-- Friday, July 03, 2020 at 09:40:28
--

	Systeme-Uniprom-MIB-V18 DEFINITIONS ::= BEGIN
 
		IMPORTS
			OBJECT-TYPE			
				FROM RFC-1212			
			TRAP-TYPE			
				FROM RFC-1215			
			enterprises			
				FROM RFC1155-SMI;
	
	
--
-- Node definitions
--
	
--  Node definitions
-- 
-- 1.3.6.1.4.1.318
		-- 1.3.6.1.4.1.318
		Systeme OBJECT IDENTIFIER ::= { enterprises 318 }

		
--  1.3.6.1.4.1.318.1
		-- 1.3.6.1.4.1.318.1
		products OBJECT IDENTIFIER ::= { Systeme 1 }

		
--  1.3.6.1.4.1.318.1.1
		-- 1.3.6.1.4.1.318.1.1
		hardware OBJECT IDENTIFIER ::= { products 1 }

		
--  1.3.6.1.4.1.318.1.1.30
		-- 1.3.6.1.4.1.318.1.1.30
		Uniprom OBJECT IDENTIFIER ::= { hardware 30 }

		
--  Uniprom Ident Table
-- 1.3.6.1.4.1.318.1.1.30.1
		-- 1.3.6.1.4.1.318.1.1.30.1
		UnipromDeviceStatusTableSize OBJECT-TYPE
			SYNTAX INTEGER
			ACCESS read-only
			STATUS mandatory
			DESCRIPTION
				"The total number of Uniprom PDUs"
			::= { Uniprom 1 }

		
--  1.3.6.1.4.1.318.1.1.30.2
		-- 1.3.6.1.4.1.318.1.1.30.2
		UnipromDevice OBJECT IDENTIFIER ::= { Uniprom 2 }

		
--  1.3.6.1.4.1.318.1.1.30.2.1
		-- 1.3.6.1.4.1.318.1.1.30.2.1
		UnipromDeviceStatusTable OBJECT-TYPE
			SYNTAX SEQUENCE OF UnipromDeviceStatusEntry
			ACCESS not-accessible
			STATUS mandatory
			::= { UnipromDevice 1 }

		
--  1.3.6.1.4.1.318.1.1.30.2.1.1
		-- 1.3.6.1.4.1.318.1.1.30.2.1.1
		UnipromDeviceStatusEntry OBJECT-TYPE
			SYNTAX UnipromDeviceStatusEntry
			ACCESS not-accessible
			STATUS mandatory
			INDEX { UnipromDeviceStatusIndex }
			::= { UnipromDeviceStatusTable 1 }

		
		UnipromDeviceStatusEntry ::=
			SEQUENCE { 
				UnipromDeviceStatusIndex
					INTEGER,
				UnipromDeviceStatusModule
					INTEGER,
				UnipromDeviceStatusVersion
					OCTET STRING,
				UnipromDeviceStatusModelNumber
					OCTET STRING,
				UnipromDeviceStatusSerialNumber
					OCTET STRING,
				UnipromDeviceStatusNumPhases
					INTEGER,
				UnipromDeviceStatusActivePower
					INTEGER,
				UnipromDeviceStatusReactivePower
					INTEGER,
				UnipromDeviceStatusApparentPower
					INTEGER,
				UnipromDeviceStatusPowerFactor
					INTEGER,
				UnipromDeviceStatusEnergy
					INTEGER,
				UnipromDeviceStatusFrequency
					INTEGER
			 }

--  1.3.6.1.4.1.318.1.1.30.2.1.1.1
		-- 1.3.6.1.4.1.318.1.1.30.2.1.1.1
		UnipromDeviceStatusIndex OBJECT-TYPE
			SYNTAX INTEGER (1..4)
			ACCESS read-only
			STATUS mandatory
			DESCRIPTION
				"The index to the Uniprom PDU status table entry"
			::= { UnipromDeviceStatusEntry 1 }

		
--  1.3.6.1.4.1.318.1.1.30.2.1.1.2
		-- 1.3.6.1.4.1.318.1.1.30.2.1.1.2
		UnipromDeviceStatusModule OBJECT-TYPE
			SYNTAX INTEGER
			ACCESS read-only
			STATUS mandatory
			DESCRIPTION
				"The user-defined Rack PDU numeric ID"
			::= { UnipromDeviceStatusEntry 2 }

		
--  1.3.6.1.4.1.318.1.1.30.2.1.1.3
		-- 1.3.6.1.4.1.318.1.1.30.2.1.1.3
		UnipromDeviceStatusVersion OBJECT-TYPE
			SYNTAX OCTET STRING
			ACCESS read-only
			STATUS mandatory
			DESCRIPTION
				"The Uniprom PDU firmware and hardware version"
			::= { UnipromDeviceStatusEntry 3 }

		
--  Exp Begin
		-- 1.3.6.1.4.1.318.1.1.30.2.1.1.4
		UnipromDeviceStatusModelNumber OBJECT-TYPE
			SYNTAX OCTET STRING
			ACCESS read-only
			STATUS mandatory
			DESCRIPTION
				"The Uniprom PDU model number"
			::= { UnipromDeviceStatusEntry 4 }

		
		-- 1.3.6.1.4.1.318.1.1.30.2.1.1.5
		UnipromDeviceStatusSerialNumber OBJECT-TYPE
			SYNTAX OCTET STRING
			ACCESS read-only
			STATUS mandatory
			DESCRIPTION
				"The Uniprom PDU serial number"
			::= { UnipromDeviceStatusEntry 5 }

		
		-- 1.3.6.1.4.1.318.1.1.30.2.1.1.6
		UnipromDeviceStatusNumPhases OBJECT-TYPE
			SYNTAX INTEGER
			ACCESS read-only
			STATUS mandatory
			DESCRIPTION
				"The number of phases present in the Uniprom PDU
				"
			::= { UnipromDeviceStatusEntry 6 }

		
--  1.3.6.1.4.1.318.1.1.30.2.1.1.4
		-- 1.3.6.1.4.1.318.1.1.30.2.1.1.7
		UnipromDeviceStatusActivePower OBJECT-TYPE
			SYNTAX INTEGER
			ACCESS read-only
			STATUS mandatory
			DESCRIPTION
				"Models that do not support this feature, 
				will respond to this OID with a value of 
				notSupported (-1).
				Indicates the PDU Active Power. Units:1 Watt"
			::= { UnipromDeviceStatusEntry 7 }

		
--  1.3.6.1.4.1.318.1.1.30.2.1.1.5
		-- 1.3.6.1.4.1.318.1.1.30.2.1.1.8
		UnipromDeviceStatusReactivePower OBJECT-TYPE
			SYNTAX INTEGER
			ACCESS read-only
			STATUS mandatory
			DESCRIPTION
				"Models that do not support this feature, 
				will respond to this OID with a value of 
				notSupported (-1).
				Indicates the PDU Reactive Power. Units:1 Var"
			::= { UnipromDeviceStatusEntry 8 }

		
--  1.3.6.1.4.1.318.1.1.30.2.1.1.6
		-- 1.3.6.1.4.1.318.1.1.30.2.1.1.9
		UnipromDeviceStatusApparentPower OBJECT-TYPE
			SYNTAX INTEGER
			ACCESS read-only
			STATUS mandatory
			DESCRIPTION
				"Models that do not support this feature, 
				will respond to this OID with a value of 
				notSupported (-1).
				Indicates the PDU Apparent Power. Units:1 VA"
			::= { UnipromDeviceStatusEntry 9 }

		
--  1.3.6.1.4.1.318.1.1.30.2.1.1.7
		-- 1.3.6.1.4.1.318.1.1.30.2.1.1.10
		UnipromDeviceStatusPowerFactor OBJECT-TYPE
			SYNTAX INTEGER
			ACCESS read-only
			STATUS mandatory
			DESCRIPTION
				"Models that do not support this feature, 
				will respond to this OID with a value of 
				notSupported (-1).
				Indicates the PDU Power Factor. Units:0.1%"
			::= { UnipromDeviceStatusEntry 10 }

		
--  1.3.6.1.4.1.318.1.1.30.2.1.1.8
		-- 1.3.6.1.4.1.318.1.1.30.2.1.1.11
		UnipromDeviceStatusEnergy OBJECT-TYPE
			SYNTAX INTEGER
			ACCESS read-only
			STATUS mandatory
			DESCRIPTION
				"Models that do not support this feature, 
				will respond to this OID with a value of 
				notSupported (-1).
				Indicates the PDU Energy. Units:1 Wh"
			::= { UnipromDeviceStatusEntry 11 }

		
--  1.3.6.1.4.1.318.1.1.30.2.1.1.9
		-- 1.3.6.1.4.1.318.1.1.30.2.1.1.12
		UnipromDeviceStatusFrequency OBJECT-TYPE
			SYNTAX INTEGER
			ACCESS read-only
			STATUS mandatory
			DESCRIPTION
				"Indicates the PDU Frequency. Units:0.001 Hz"
			::= { UnipromDeviceStatusEntry 12 }

		
--  1.3.6.1.4.1.318.1.1.30.2.2
		-- 1.3.6.1.4.1.318.1.1.30.2.2
		UnipromDeviceControlTable OBJECT-TYPE
			SYNTAX SEQUENCE OF UnipromDeviceControlEntry
			ACCESS not-accessible
			STATUS mandatory
			::= { UnipromDevice 2 }

		
--  1.3.6.1.4.1.318.1.1.30.2.2.1
		-- 1.3.6.1.4.1.318.1.1.30.2.2.1
		UnipromDeviceControlEntry OBJECT-TYPE
			SYNTAX UnipromDeviceControlEntry
			ACCESS not-accessible
			STATUS mandatory
			INDEX { UnipromDeviceControlIndex }
			::= { UnipromDeviceControlTable 1 }

		
		UnipromDeviceControlEntry ::=
			SEQUENCE { 
				UnipromDeviceControlIndex
					INTEGER,
				UnipromDeviceControlModule
					INTEGER,
				UnipromDeviceControlReboot
					INTEGER,
				UnipromDeviceControlEngeryReset
					INTEGER,
				UnipromDeviceControlBeepAlarm
					INTEGER,
				UnipromDeviceControlParameterReset
					INTEGER	
			 }

--  1.3.6.1.4.1.318.1.1.30.2.2.1.1
		-- 1.3.6.1.4.1.318.1.1.30.2.2.1.1
		UnipromDeviceControlIndex OBJECT-TYPE
			SYNTAX INTEGER (1..4)
			ACCESS read-only
			STATUS mandatory
			DESCRIPTION
				"The index to the Uniprom PDU control table entry"
			::= { UnipromDeviceControlEntry 1 }

		
--  1.3.6.1.4.1.318.1.1.30.2.2.1.2
		-- 1.3.6.1.4.1.318.1.1.30.2.2.1.2
		UnipromDeviceControlModule OBJECT-TYPE
			SYNTAX INTEGER
			ACCESS read-only
			STATUS mandatory
			DESCRIPTION
				"The user-defined Uniprom PDU numeric ID"
			::= { UnipromDeviceControlEntry 2 }

		
--  1.3.6.1.4.1.318.1.1.30.2.2.1.3
		-- 1.3.6.1.4.1.318.1.1.30.2.2.1.3
		UnipromDeviceControlReboot OBJECT-TYPE
			SYNTAX INTEGER
				{
				noOperation(1),
				reboot(2)
				}
			ACCESS read-write
			STATUS mandatory
			DESCRIPTION
				"Setting this OID to reboot (1) will cause 
				the device reboot immediately.
				Getting this OID in models that support this 
				feature will do nothing and return the 
				noOperation(0) value."
			::= { UnipromDeviceControlEntry 3 }

		
--  1.3.6.1.4.1.318.1.1.30.2.2.1.4
		-- 1.3.6.1.4.1.318.1.1.30.2.2.1.4
		UnipromDeviceControlEngeryReset OBJECT-TYPE
			SYNTAX INTEGER
				{
				reset(1)
				}
			ACCESS read-write
			STATUS mandatory
			DESCRIPTION
				"Setting this OID to reboot (1) will cause 
				the device reboot immediately.
				Getting this OID in models that support this 
				feature will do nothing and return the 
				noOperation(0) value."
			::= { UnipromDeviceControlEntry 4 }

		
--  1.3.6.1.4.1.318.1.1.30.2.2.1.5
		-- 1.3.6.1.4.1.318.1.1.30.2.2.1.5
		UnipromDeviceControlBeepAlarm OBJECT-TYPE
			SYNTAX INTEGER
				{
				off(1),
				on(2)
				}
			ACCESS read-write
			STATUS mandatory
			DESCRIPTION
				"User-defined Beep alarm, 1 for turn off Beep, 2 for turn on Beep.
				Models that do not support this feature will respond to this OID
				with a value of -1."
			::= { UnipromDeviceControlEntry 5 }

--  1.3.6.1.4.1.318.1.1.30.2.2.1.6
		-- 1.3.6.1.4.1.318.1.1.30.2.2.1.6
		UnipromDeviceControlParameterReset OBJECT-TYPE
			SYNTAX INTEGER
				{
				noOperation(0),
				reset(1)
				}
			ACCESS read-write
			STATUS mandatory
			DESCRIPTION
				"Setting this OID to reset (1) will cause the device to immediately restore the set parameters to their factory settings.
				Obtaining this OID function in a model that supports this operation will not perform any operation and will return
				The value of noOperation (0)."
			::= { UnipromDeviceControlEntry 6 }
		
--  Uniprom Phase Data
-- 1.3.6.1.4.1.318.1.1.30.3
		-- 1.3.6.1.4.1.318.1.1.30.3
		UnipromPhaseTableSize OBJECT-TYPE
			SYNTAX INTEGER
			ACCESS read-only
			STATUS mandatory
			DESCRIPTION
				"The number of connected Uniprom PDU phases"
			::= { Uniprom 3 }

		
--  1.3.6.1.4.1.318.1.1.30.4
		-- 1.3.6.1.4.1.318.1.1.30.4
		UnipromPhase OBJECT IDENTIFIER ::= { Uniprom 4 }

		
--  1.3.6.1.4.1.318.1.1.30.4.1
		-- 1.3.6.1.4.1.318.1.1.30.4.1
		UnipromPhaseConfigTable OBJECT-TYPE
			SYNTAX SEQUENCE OF UnipromPhaseConfigEntry
			ACCESS not-accessible
			STATUS mandatory
			::= { UnipromPhase 1 }

		
--  1.3.6.1.4.1.318.1.1.30.4.1.1
		-- 1.3.6.1.4.1.318.1.1.30.4.1.1
		UnipromPhaseConfigEntry OBJECT-TYPE
			SYNTAX UnipromPhaseConfigEntry
			ACCESS not-accessible
			STATUS mandatory
			INDEX { UnipromPhaseConfigIndex }
			::= { UnipromPhaseConfigTable 1 }

		
		UnipromPhaseConfigEntry ::=
			SEQUENCE { 
				UnipromPhaseConfigIndex
					INTEGER,
				UnipromPhaseConfigModule
					INTEGER,
				UnipromPhaseConfigNumber
					INTEGER,
				UnipromPhaseConfigOverVoltageThreshold
					INTEGER,
				UnipromPhaseConfigLowVoltageThreshold
					INTEGER,
				UnipromPhaseConfigOverCurrentThreshold
					INTEGER,
				UnipromPhaseConfigLowCurrentThreshold
					INTEGER
			 }

--  1.3.6.1.4.1.318.1.1.30.4.1.1.1
		-- 1.3.6.1.4.1.318.1.1.30.4.1.1.1
		UnipromPhaseConfigIndex OBJECT-TYPE
			SYNTAX INTEGER (1..12)
			ACCESS read-only
			STATUS mandatory
			DESCRIPTION
				"The index to the Uniprom PDU phase configuration
				table entry"
			::= { UnipromPhaseConfigEntry 1 }

		
--  1.3.6.1.4.1.318.1.1.30.4.1.1.2
		-- 1.3.6.1.4.1.318.1.1.30.4.1.1.2
		UnipromPhaseConfigModule OBJECT-TYPE
			SYNTAX INTEGER
			ACCESS read-only
			STATUS mandatory
			DESCRIPTION
				"The user-defined Uniprom PDU numeric ID"
			::= { UnipromPhaseConfigEntry 2 }

		
--  1.3.6.1.4.1.318.1.1.30.4.1.1.3
		-- 1.3.6.1.4.1.318.1.1.30.4.1.1.3
		UnipromPhaseConfigNumber OBJECT-TYPE
			SYNTAX INTEGER
			ACCESS read-only
			STATUS mandatory
			DESCRIPTION
				"The numeric phase ID"
			::= { UnipromPhaseConfigEntry 3 }

		
--  1.3.6.1.4.1.318.1.1.30.4.1.1.4
		-- 1.3.6.1.4.1.318.1.1.30.4.1.1.4
		UnipromPhaseConfigOverVoltageThreshold OBJECT-TYPE
			SYNTAX INTEGER
			ACCESS read-write
			STATUS mandatory
			DESCRIPTION
				"User-defined Phase Over Voltage alarm threshold. 
				Models that do not support this feature will
				respond to this OID with a value of -1.
				Units:0.1 V"
			::= { UnipromPhaseConfigEntry 4 }

		
--  1.3.6.1.4.1.318.1.1.30.4.1.1.5
		-- 1.3.6.1.4.1.318.1.1.30.4.1.1.5
		UnipromPhaseConfigLowVoltageThreshold OBJECT-TYPE
			SYNTAX INTEGER
			ACCESS read-write
			STATUS mandatory
			DESCRIPTION
				"User-defined Phase Low Voltage alarm threshold. 
				Models that do not support this feature will
				respond to this OID with a value of -1.
				Units:0.1 V"
			::= { UnipromPhaseConfigEntry 5 }

		
--  1.3.6.1.4.1.318.1.1.30.4.1.1.6
		-- 1.3.6.1.4.1.318.1.1.30.4.1.1.6
		UnipromPhaseConfigOverCurrentThreshold OBJECT-TYPE
			SYNTAX INTEGER
			ACCESS read-write
			STATUS mandatory
			DESCRIPTION
				"User-defined Phase Over Current alarm threshold. 
				Models that do not support this feature will
				respond to this OID with a value of -1.
				Units:0.01 A"
			::= { UnipromPhaseConfigEntry 6 }

		
--  1.3.6.1.4.1.318.1.1.30.4.1.1.7
		-- 1.3.6.1.4.1.318.1.1.30.4.1.1.7
		UnipromPhaseConfigLowCurrentThreshold OBJECT-TYPE
			SYNTAX INTEGER
			ACCESS read-write
			STATUS mandatory
			DESCRIPTION
				"User-defined Phase Low Current alarm threshold. 
				Models that do not support this feature will
				respond to this OID with a value of -1.
				Units:0.01 A"
			::= { UnipromPhaseConfigEntry 7 }

		
--  1.3.6.1.4.1.318.1.1.30.4.2
		-- 1.3.6.1.4.1.318.1.1.30.4.2
		UnipromPhaseStatusTable OBJECT-TYPE
			SYNTAX SEQUENCE OF UnipromPhaseStatusEntry
			ACCESS not-accessible
			STATUS mandatory
			::= { UnipromPhase 2 }

		
--  1.3.6.1.4.1.318.1.1.30.4.2.1
		-- 1.3.6.1.4.1.318.1.1.30.4.2.1
		UnipromPhaseStatusEntry OBJECT-TYPE
			SYNTAX UnipromPhaseStatusEntry
			ACCESS not-accessible
			STATUS mandatory
			INDEX { UnipromPhaseStatusIndex }
			::= { UnipromPhaseStatusTable 1 }

		
		UnipromPhaseStatusEntry ::=
			SEQUENCE { 
				UnipromPhaseStatusIndex
					INTEGER,
				UnipromPhaseStatusModule
					INTEGER,
				UnipromPhaseStatusNumber
					INTEGER,
				UnipromPhaseStatusVoltage
					INTEGER,
				UnipromPhaseStatusCurrent
					INTEGER,
				UnipromPhaseStatusActivePower
					INTEGER,
				UnipromPhaseStatusReactivePower
					INTEGER,
				UnipromPhaseStatusApparentPower
					INTEGER,
				UnipromPhaseStatusPowerFactor
					INTEGER,
				UnipromPhaseStatusEnergy
					INTEGER
			 }

--  1.3.6.1.4.1.318.1.1.30.4.2.1.1
		-- 1.3.6.1.4.1.318.1.1.30.4.2.1.1
		UnipromPhaseStatusIndex OBJECT-TYPE
			SYNTAX INTEGER (1..12)
			ACCESS read-only
			STATUS mandatory
			DESCRIPTION
				"The index to the Uniprom PDU phase configuration
				table entry"
			::= { UnipromPhaseStatusEntry 1 }

		
--  1.3.6.1.4.1.318.1.1.30.4.2.1.2
		-- 1.3.6.1.4.1.318.1.1.30.4.2.1.2
		UnipromPhaseStatusModule OBJECT-TYPE
			SYNTAX INTEGER
			ACCESS read-only
			STATUS mandatory
			DESCRIPTION
				"The user-defined Uniprom PDU numeric ID"
			::= { UnipromPhaseStatusEntry 2 }

		
--  1.3.6.1.4.1.318.1.1.30.4.2.1.3
		-- 1.3.6.1.4.1.318.1.1.30.4.2.1.3
		UnipromPhaseStatusNumber OBJECT-TYPE
			SYNTAX INTEGER
			ACCESS read-only
			STATUS mandatory
			DESCRIPTION
				"The numeric phase ID"
			::= { UnipromPhaseStatusEntry 3 }

		
--  1.3.6.1.4.1.318.1.1.30.4.2.1.4
		-- 1.3.6.1.4.1.318.1.1.30.4.2.1.4
		UnipromPhaseStatusVoltage OBJECT-TYPE
			SYNTAX INTEGER
			ACCESS read-only
			STATUS mandatory
			DESCRIPTION
				"Indicates the Phase Voltage. Units:0.1 V"
			::= { UnipromPhaseStatusEntry 4 }

		
--  1.3.6.1.4.1.318.1.1.30.4.2.1.5
		-- 1.3.6.1.4.1.318.1.1.30.4.2.1.5
		UnipromPhaseStatusCurrent OBJECT-TYPE
			SYNTAX INTEGER
			ACCESS read-only
			STATUS mandatory
			DESCRIPTION
				"Indicates the Phase Current. Units:0.01 A"
			::= { UnipromPhaseStatusEntry 5 }

		
--  1.3.6.1.4.1.318.1.1.30.4.2.1.6
		-- 1.3.6.1.4.1.318.1.1.30.4.2.1.6
		UnipromPhaseStatusActivePower OBJECT-TYPE
			SYNTAX INTEGER
			ACCESS read-only
			STATUS mandatory
			DESCRIPTION
				"Indicates the Phase Active Power. Units:1 Watt"
			::= { UnipromPhaseStatusEntry 6 }

		
--  1.3.6.1.4.1.318.1.1.30.4.2.1.7
		-- 1.3.6.1.4.1.318.1.1.30.4.2.1.7
		UnipromPhaseStatusReactivePower OBJECT-TYPE
			SYNTAX INTEGER
			ACCESS read-only
			STATUS mandatory
			DESCRIPTION
				"Models that do not support this feature, 
				will respond to this OID with a value of 
				notSupported (-1).
				Indicates the Phase Reactive Power. Units:1 Var"
			::= { UnipromPhaseStatusEntry 7 }

		
--  1.3.6.1.4.1.318.1.1.30.4.2.1.8
		-- 1.3.6.1.4.1.318.1.1.30.4.2.1.8
		UnipromPhaseStatusApparentPower OBJECT-TYPE
			SYNTAX INTEGER
			ACCESS read-only
			STATUS mandatory
			DESCRIPTION
				"Models that do not support this feature, 
				will respond to this OID with a value of 
				notSupported (-1).
				Indicates the Phase Apparent Power. Units:1 VA"
			::= { UnipromPhaseStatusEntry 8 }

		
--  1.3.6.1.4.1.318.1.1.30.4.2.1.9
		-- 1.3.6.1.4.1.318.1.1.30.4.2.1.9
		UnipromPhaseStatusPowerFactor OBJECT-TYPE
			SYNTAX INTEGER
			ACCESS read-only
			STATUS mandatory
			DESCRIPTION
				"Indicates the Phase Power Factor. Units:0.1%"
			::= { UnipromPhaseStatusEntry 9 }

		
--  1.3.6.1.4.1.318.1.1.30.4.2.1.10
		-- 1.3.6.1.4.1.318.1.1.30.4.2.1.10
		UnipromPhaseStatusEnergy OBJECT-TYPE
			SYNTAX INTEGER
			ACCESS read-only
			STATUS mandatory
			DESCRIPTION
				"Indicates the Phase Energy. Units:1 Wh"
			::= { UnipromPhaseStatusEntry 10 }

		
--  Uniprom Switched Outlet Data
-- 1.3.6.1.4.1.318.1.1.30.5
		-- 1.3.6.1.4.1.318.1.1.30.5
		UnipromOutletTableSize OBJECT-TYPE
			SYNTAX INTEGER
			ACCESS read-only
			STATUS mandatory
			DESCRIPTION
				"The number of switched outlets on connected Uniprom PDUs."
			::= { Uniprom 5 }

		
--  1.3.6.1.4.1.318.1.1.30.6
		-- 1.3.6.1.4.1.318.1.1.30.6
		UnipromOutlet OBJECT IDENTIFIER ::= { Uniprom 6 }

		
--  1.3.6.1.4.1.318.1.1.30.6.1
		-- 1.3.6.1.4.1.318.1.1.30.6.1
		UnipromOutletStatusTable OBJECT-TYPE
			SYNTAX SEQUENCE OF UnipromOutletStatusEntry
			ACCESS not-accessible
			STATUS mandatory
			::= { UnipromOutlet 1 }

		
--  1.3.6.1.4.1.318.1.1.30.6.1.1
		-- 1.3.6.1.4.1.318.1.1.30.6.1.1
		UnipromOutletStatusEntry OBJECT-TYPE
			SYNTAX UnipromOutletStatusEntry
			ACCESS not-accessible
			STATUS mandatory
			INDEX { UnipromOutletStatusIndex }
			::= { UnipromOutletStatusTable 1 }

		
		UnipromOutletStatusEntry ::=
			SEQUENCE { 
				UnipromOutletStatusIndex
					INTEGER,
				UnipromOutletStatusModule
					INTEGER,
				UnipromOutletStatusNumber
					INTEGER,
				UnipromOutletStatusState
					INTEGER
			 }

--  1.3.6.1.4.1.318.1.1.30.6.1.1.1
		-- 1.3.6.1.4.1.318.1.1.30.6.1.1.1
		UnipromOutletStatusIndex OBJECT-TYPE
			SYNTAX INTEGER (1..128)
			ACCESS read-only
			STATUS mandatory
			DESCRIPTION
				"The index to the Uniprom PDU switched outlet
				status information table entry.
				Models that do not support this feature, 
				will respond to this OID with a value of 
				notSupported (-1)."
			::= { UnipromOutletStatusEntry 1 }

		
--  Models that do not support this feature, 
-- will respond to this OID with a value of 
-- notSupported (-1).
-- 1.3.6.1.4.1.318.1.1.30.6.1.1.2
		-- 1.3.6.1.4.1.318.1.1.30.6.1.1.2
		UnipromOutletStatusModule OBJECT-TYPE
			SYNTAX INTEGER
			ACCESS read-only
			STATUS mandatory
			DESCRIPTION
				"The user-defined Uniprom PDU numeric ID.
				Models that do not support this feature, 
				will respond to this OID with a value of 
				notSupported (-1)."
			::= { UnipromOutletStatusEntry 2 }

		
--  Models that do not support this feature, 
-- will respond to this OID with a value of 
-- notSupported (-1).
-- 1.3.6.1.4.1.318.1.1.30.6.1.1.3
		-- 1.3.6.1.4.1.318.1.1.30.6.1.1.3
		UnipromOutletStatusNumber OBJECT-TYPE
			SYNTAX INTEGER
			ACCESS read-only
			STATUS mandatory
			DESCRIPTION
				"The numeric switched outlet ID.
				Models that do not support this feature, 
				will respond to this OID with a value of 
				notSupported (-1)."
			::= { UnipromOutletStatusEntry 3 }

		
--  1.3.6.1.4.1.318.1.1.30.6.1.1.4
		-- 1.3.6.1.4.1.318.1.1.30.6.1.1.4
		UnipromOutletStatusState OBJECT-TYPE
			SYNTAX INTEGER
				{
				off(1),
				on(2)
				}
			ACCESS read-only
			STATUS mandatory
			DESCRIPTION
				"Indicates the present switch state of the Uniprom
				PDU switched outlet being queried.
				Models that do not support this feature, 
				will respond to this OID with a value of 
				notSupported (-1)."
			::= { UnipromOutletStatusEntry 4 }

		
--  1.3.6.1.4.1.318.1.1.30.6.2
		-- 1.3.6.1.4.1.318.1.1.30.6.2
		UnipromOutletControlTable OBJECT-TYPE
			SYNTAX SEQUENCE OF UnipromOutletControlEntry
			ACCESS not-accessible
			STATUS mandatory
			::= { UnipromOutlet 2 }

		
--  1.3.6.1.4.1.318.1.1.30.6.2.1
		-- 1.3.6.1.4.1.318.1.1.30.6.2.1
		UnipromOutletControlEntry OBJECT-TYPE
			SYNTAX UnipromOutletControlEntry
			ACCESS not-accessible
			STATUS mandatory
			INDEX { UnipromOutletControlIndex }
			::= { UnipromOutletControlTable 1 }

		
		UnipromOutletControlEntry ::=
			SEQUENCE { 
				UnipromOutletControlIndex
					INTEGER,
				UnipromOutletControlModule
					INTEGER,
				UnipromOutletControlNumber
					INTEGER,
				UnipromOutletControlCommand
					INTEGER
			 }

--  1.3.6.1.4.1.318.1.1.30.6.2.1.1
		-- 1.3.6.1.4.1.318.1.1.30.6.2.1.1
		UnipromOutletControlIndex OBJECT-TYPE
			SYNTAX INTEGER (1..128)
			ACCESS read-only
			STATUS mandatory
			DESCRIPTION
				"The index to the Uniprom PDU switched outlet
				configuration table entry.
				Models that do not support this feature, 
				will respond to this OID with a value of 
				notSupported (-1)."
			::= { UnipromOutletControlEntry 1 }

		
--  1.3.6.1.4.1.318.1.1.30.6.2.1.2
		-- 1.3.6.1.4.1.318.1.1.30.6.2.1.2
		UnipromOutletControlModule OBJECT-TYPE
			SYNTAX INTEGER
			ACCESS read-only
			STATUS mandatory
			DESCRIPTION
				"The user-defined Uniprom PDU numeric ID.
				Models that do not support this feature, 
				will respond to this OID with a value of 
				notSupported (-1)."
			::= { UnipromOutletControlEntry 2 }

		
--  1.3.6.1.4.1.318.1.1.30.6.2.1.3
		-- 1.3.6.1.4.1.318.1.1.30.6.2.1.3
		UnipromOutletControlNumber OBJECT-TYPE
			SYNTAX INTEGER
			ACCESS read-only
			STATUS mandatory
			DESCRIPTION
				"The numeric switched outlet ID.
				Models that do not support this feature, 
				will respond to this OID with a value of 
				notSupported (-1)."
			::= { UnipromOutletControlEntry 3 }

		
--  1.3.6.1.4.1.318.1.1.30.6.2.1.4
		-- 1.3.6.1.4.1.318.1.1.30.6.2.1.4
		UnipromOutletControlCommand OBJECT-TYPE
			SYNTAX INTEGER
				{
				immediateOn(1),
				immediateOff(2),
				outletUnknown(3)
				}
			ACCESS read-write
			STATUS mandatory
			DESCRIPTION
				"Getting this variable will return the outlet state. If
				the outlet is on, the immediateOn (1) value will be returned.
				If the outlet is off, the immediateOff (2) value will be
				returned. If the state of the outlet cannot be
				determined, the outletUnknown (3) value will be returned.
				If the outletUnknown condition should occur, all devices
				powered by the PDU should be shut down. The PDU's power
				should then be cycled to clear this condition.
				Models that do not support this feature, 
				will respond to this OID with a value of 
				notSupported (-1).
				
				Setting this variable to immediateOn (1) will immediately turn
				the outlet on.
				
				Setting this variable to immediateOff (2) will immediately turn
				the outlet off."
			::= { UnipromOutletControlEntry 4 }

		
--  Uniprom Temperature and Humidity Sensor Data
-- 1.3.6.1.4.1.318.1.1.30.7
		-- 1.3.6.1.4.1.318.1.1.30.7
		UnipromSensorTableSize OBJECT-TYPE
			SYNTAX INTEGER
			ACCESS read-only
			STATUS mandatory
			DESCRIPTION
				"The number of connected temperature-humidity sensors"
			::= { Uniprom 7 }

		
--  1.3.6.1.4.1.318.1.1.30.8
		-- 1.3.6.1.4.1.318.1.1.30.8
		UnipromSensor OBJECT IDENTIFIER ::= { Uniprom 8 }

		
--  1.3.6.1.4.1.318.1.1.30.8.1
		-- 1.3.6.1.4.1.318.1.1.30.8.1
		UnipromSensorConfigTable OBJECT-TYPE
			SYNTAX SEQUENCE OF UnipromSensorConfigEntry
			ACCESS not-accessible
			STATUS mandatory
			::= { UnipromSensor 1 }

		
--  1.3.6.1.4.1.318.1.1.30.8.1.1
		-- 1.3.6.1.4.1.318.1.1.30.8.1.1
		UnipromSensorConfigEntry OBJECT-TYPE
			SYNTAX UnipromSensorConfigEntry
			ACCESS not-accessible
			STATUS mandatory
			INDEX { UnipromSensorConfigIndex }
			::= { UnipromSensorConfigTable 1 }

		
		UnipromSensorConfigEntry ::=
			SEQUENCE { 
				UnipromSensorConfigIndex
					INTEGER,
				UnipromSensorConfigModule
					INTEGER,
				UnipromSensorConfigTempMaxThreshold
					INTEGER,
				UnipromSensorConfigTempMinThreshold
					INTEGER,
				UnipromSensorConfigHumidityMaxThreshold
					INTEGER,
				UnipromSensorConfigHumidityMinThreshold
					INTEGER
			 }

--  1.3.6.1.4.1.318.1.1.30.8.1.1.1
		-- 1.3.6.1.4.1.318.1.1.30.8.1.1.1
		UnipromSensorConfigIndex OBJECT-TYPE
			SYNTAX INTEGER (1..4)
			ACCESS read-only
			STATUS mandatory
			DESCRIPTION
				"The index to the temperature-humidity sensor
				configuration data table entry"
			::= { UnipromSensorConfigEntry 1 }

		
--  1.3.6.1.4.1.318.1.1.30.8.1.1.2
		-- 1.3.6.1.4.1.318.1.1.30.8.1.1.2
		UnipromSensorConfigModule OBJECT-TYPE
			SYNTAX INTEGER
			ACCESS read-only
			STATUS mandatory
			DESCRIPTION
				"The user-defined Uniprom PDU numeric ID"
			::= { UnipromSensorConfigEntry 2 }

		
--  1.3.6.1.4.1.318.1.1.30.8.1.1.3
		-- 1.3.6.1.4.1.318.1.1.30.8.1.1.3
		UnipromSensorConfigTempMaxThreshold OBJECT-TYPE
			SYNTAX INTEGER
			ACCESS read-write
			STATUS mandatory
			DESCRIPTION
				"User-defined Max Temperature alarm threshold. 
				Models that do not support this feature will
				respond to this OID with a value of -1.
				Units: 0.1 ??"
			::= { UnipromSensorConfigEntry 3 }

		
--  1.3.6.1.4.1.318.1.1.30.8.1.1.4
		-- 1.3.6.1.4.1.318.1.1.30.8.1.1.4
		UnipromSensorConfigTempMinThreshold OBJECT-TYPE
			SYNTAX INTEGER
			ACCESS read-write
			STATUS mandatory
			DESCRIPTION
				"User-defined Min Temperature alarm threshold. 
				Models that do not support this feature will
				respond to this OID with a value of -1.
				Units: 0.1 ??"
			::= { UnipromSensorConfigEntry 4 }

		
--  1.3.6.1.4.1.318.1.1.30.8.1.1.5
		-- 1.3.6.1.4.1.318.1.1.30.8.1.1.5
		UnipromSensorConfigHumidityMaxThreshold OBJECT-TYPE
			SYNTAX INTEGER
			ACCESS read-write
			STATUS mandatory
			DESCRIPTION
				"User-defined Max Humidity alarm threshold. 
				Models that do not support this feature will
				respond to this OID with a value of -1.
				Units: 0.1% RH"
			::= { UnipromSensorConfigEntry 5 }

		
--  1.3.6.1.4.1.318.1.1.30.8.1.1.6
		-- 1.3.6.1.4.1.318.1.1.30.8.1.1.6
		UnipromSensorConfigHumidityMinThreshold OBJECT-TYPE
			SYNTAX INTEGER
			ACCESS read-write
			STATUS mandatory
			DESCRIPTION
				"User-defined Min Humidity alarm threshold. 
				Models that do not support this feature will
				respond to this OID with a value of -1.
				Units: 0.1% RH"
			::= { UnipromSensorConfigEntry 6 }

		
--  1.3.6.1.4.1.318.1.1.30.8.2
		-- 1.3.6.1.4.1.318.1.1.30.8.2
		UnipromSensorStatusTable OBJECT-TYPE
			SYNTAX SEQUENCE OF UnipromSensorStatusEntry
			ACCESS not-accessible
			STATUS mandatory
			::= { UnipromSensor 2 }

		
--  1.3.6.1.4.1.318.1.1.30.8.2.1
		-- 1.3.6.1.4.1.318.1.1.30.8.2.1
		UnipromSensorStatusEntry OBJECT-TYPE
			SYNTAX UnipromSensorStatusEntry
			ACCESS not-accessible
			STATUS mandatory
			INDEX { UnipromSensorStatusIndex }
			::= { UnipromSensorStatusTable 1 }

		
		UnipromSensorStatusEntry ::=
			SEQUENCE { 
				UnipromSensorStatusIndex
					INTEGER,
				UnipromSensorStatusModule
					INTEGER,
				UnipromSensorStatusTemperature
					INTEGER,
				UnipromSensorStatusHumidity
					INTEGER
			 }

--  1.3.6.1.4.1.318.1.1.30.8.2.1.1
		-- 1.3.6.1.4.1.318.1.1.30.8.2.1.1
		UnipromSensorStatusIndex OBJECT-TYPE
			SYNTAX INTEGER (1..4)
			ACCESS read-only
			STATUS mandatory
			DESCRIPTION
				"The index to the temperature-humidity
				status data table entry"
			::= { UnipromSensorStatusEntry 1 }

		
--  1.3.6.1.4.1.318.1.1.30.8.2.1.2
		-- 1.3.6.1.4.1.318.1.1.30.8.2.1.2
		UnipromSensorStatusModule OBJECT-TYPE
			SYNTAX INTEGER
			ACCESS read-only
			STATUS mandatory
			DESCRIPTION
				"The user-defined Uniprom PDU numeric ID"
			::= { UnipromSensorStatusEntry 2 }

		
--  1.3.6.1.4.1.318.1.1.30.8.2.1.3
		-- 1.3.6.1.4.1.318.1.1.30.8.2.1.3
		UnipromSensorStatusTemperature OBJECT-TYPE
			SYNTAX INTEGER
			ACCESS read-only
			STATUS mandatory
			DESCRIPTION
				"Sensor temperature reading in tenths of degrees Celsius. Units:0.1 ??"
			::= { UnipromSensorStatusEntry 3 }

		
--  1.3.6.1.4.1.318.1.1.30.8.2.1.4
		-- 1.3.6.1.4.1.318.1.1.30.8.2.1.4
		UnipromSensorStatusHumidity OBJECT-TYPE
			SYNTAX INTEGER
			ACCESS read-only
			STATUS mandatory
			DESCRIPTION
				"Sensor humidity reading in percent relative humidity. Units:0.1% RH"
			::= { UnipromSensorStatusEntry 4 }

		
	
--
-- Trap definitions
--
	
--  Trap definitions
-- 
		UnipromCriticalCondition TRAP-TYPE 
			ENTERPRISE Uniprom
			VARIABLES { UnipromPhaseStatusVoltage, UnipromPhaseStatusCurrent, UnipromSensorStatusTemperature, UnipromSensorStatusHumidity }
			DESCRIPTION 
				"SEVERE: A Uniprom critical condition has been detected.
				The first variable is the device number.
				The second variable is the instance number.
				The third variable is the trap text message."
			::=  812

		UnipromCriticalConditionCleared TRAP-TYPE 
			ENTERPRISE Uniprom
			VARIABLES { UnipromPhaseStatusVoltage, UnipromPhaseStatusCurrent, UnipromSensorStatusTemperature, UnipromSensorStatusHumidity }
			DESCRIPTION 
				"INFORMATIONAL: A Uniprom critical condition has been cleared.
				The first variable is the device number.
				The second variable is the instance number.
				The third variable is the trap text message."
			::=  813

		UnipromWarningCondition TRAP-TYPE 
			ENTERPRISE Uniprom
			VARIABLES { UnipromPhaseStatusVoltage, UnipromPhaseStatusCurrent, UnipromSensorStatusTemperature, UnipromSensorStatusHumidity }
			DESCRIPTION 
				"SEVERE: A Uniprom warnning condition has been detected.
				The first variable is the device number.
				The second variable is the instance number.
				The third variable is the trap text message."
			::=  814

		UnipromWarningConditionCleared TRAP-TYPE 
			ENTERPRISE Uniprom
			VARIABLES { UnipromPhaseStatusVoltage, UnipromPhaseStatusCurrent, UnipromSensorStatusTemperature, UnipromSensorStatusHumidity }
			DESCRIPTION 
				"SEVERE: A Uniprom warnning condition has been cleared.
				The first variable is the device number.
				The second variable is the instance number.
				The third variable is the trap text message."
			::=  815

	
	END

--
-- Systeme-Uniprom-MIB-V1.8.my
--
